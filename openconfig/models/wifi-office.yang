module wifi-office {

  yang-version "1";

  // namespace
  namespace "http://google.com/yang/wifi/wifi-office";

  // Assign this module a prefix to be used by other modules, when imported.
  prefix "wifi-office";

  import openconfig-system {prefix oc-sys; }
  import openconfig-wifi-phy { prefix wifi-phy; }
  import openconfig-wifi-mac { prefix wifi-mac; }
  import openconfig-inet-types { prefix oc-inet; }

  // meta
  organization "Google, Inc.";

  contact
    "Google, Inc.
    1600 Amphitheatre Pkway
    Mountain View, CA 94043
    www.google.com";

  description
    "This module defines the top level WiFi Configurations for an office.";

  revision "2017-07-27" {
    description
      "Initial version";
    reference "0.1.0";
  }

  grouping vendor-specific-config {
    description
      "Configurations specific to a certain vendor.";

    list vendor-config {
      key "config-key";
      description
        "The name associated with this configuration.";

      leaf config-key {
        type string;
        description
          "The key associated with this configuration.";
      }

      leaf config-value {
        type string;
        description
        "The value of this configuration.";
      }
    }
  }

  grouping supported-vendor {
    description
      "Vendors supported in the site.";

    list vendor {
      key "vendor-name";
      description
        "The list of vendors supported in the site.";

      leaf vendor-name {
        type string;
        description
          "Name of the vendor. Unique within the site.";
      }
    }
  }

  grouping wifi-office-top {
    description
      "Top-level grouping for office configuration & state data.";

    leaf office-name {
      type string;
      description
        "The name associated with this office.";
    }

    uses supported-vendor;

    list office-ap {
      key "hostname";
      description
        "AP FQDN";

      leaf hostname {
        type oc-inet:domain-name;
        description
          "AP FQDN";
      }

      leaf vendor {
        type string;
        description
          "The name of vendor for this AP.";
      }

      uses oc-sys:system-top;
      uses wifi-phy:radio-top;
      uses wifi-mac:ssid-top;
      uses vendor-specific-config;
    }

    uses vendor-specific-config;
  }

  uses wifi-office-top;
}
