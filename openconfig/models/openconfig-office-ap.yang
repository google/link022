module openconfig-office-ap {

  yang-version "1";

  // namespace
  namespace "http://google.com/yang/wifi/office-ap";

  // Assign this module a prefix to be used by other modules, when imported.
  prefix "oc-office-ap";

  import openconfig-system {prefix oc-sys; }
  import openconfig-wifi-phy { prefix wifi-phy; }
  import openconfig-wifi-mac { prefix wifi-mac; }
  import openconfig-inet-types { prefix oc-inet; }

  // meta
  organization "Google, Inc.";

  contact
    "Google, Inc.
    1600 Amphitheatre Pkway
    Mountain View, CA 94043
    www.google.com";

  description
    "This module defines the top level WiFi Configurations for an AP.";

  revision "2017-12-04" {
    description
      "Initial version";
    reference "0.1.0";
  }

  grouping vendor-specific-config {
    description
      "Configurations specific to a certain vendor.";

    list vendor-config {
      key "config-key";
      description
        "The name associated with this configuration.";

      leaf config-key {
        type string;
        description
          "The key associated with this configuration.";
      }

      leaf config-value {
        type string;
        description
        "The value of this configuration.";
      }
    }
  }

  grouping office-ap-top {
    description
      "Top-level grouping for AP configuration & state data.";

    leaf hostname {
      type oc-inet:domain-name;
      description
        "AP FQDN";
    }

    uses oc-sys:system-top;
    uses wifi-phy:radio-top;
    uses wifi-mac:ssid-top;
    uses vendor-specific-config;

  }

  uses office-ap-top;
}
